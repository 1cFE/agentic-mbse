package fx {
    private import ScalarValues::*;
    part def Site {
        attribute a : Real = 0.9;
        attribute b : Real = 0.8;
        assert constraint c { ScalarFunctions::max(a, b) < 1.0 }
    }
    part site : Site;
}
