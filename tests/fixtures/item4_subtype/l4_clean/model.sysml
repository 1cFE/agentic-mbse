// Item-4 level-4 silent-on-clean fixture: attributes, no constraints at all.
package L4Clean {
    private import ScalarValues::*;
    part def Gadget {
        attribute size : Real = 3.0;
        attribute mass : Real = 1.0;
    }
}
